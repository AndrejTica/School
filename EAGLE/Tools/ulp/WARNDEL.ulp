// THIS PROGRAM IS PROVIDED AS IS AND WITHOUT WARRANTY OF ANY KIND,
// EXPRESSED OR IMPLIED.

//  Author: <alf@cadsoft.de>

/*  This ULP generates a Script which deletes the warnings and error 
 *  messages in layer 199 along with the layer itself.
 *  
 *  It complements EXTD_ERC.ULP in case you forget to use WARNDEL.SCR
 *  before using EXTD_ERC.ULP once more.
 *  Please note that the file WARNDEL.SCR will be overwritten after
 *  EXTD_ERC.ULP has been started and you will loose the previous   
 *  delete information.
 */

/*  Dieses ULP erzeugt ein Script, um die Warnungen und Fehlermeldungen
 *  im Layer 199 zu löschen, einschließlich den Layer selbst.
 *  
 *  Es ist als Ergaenzug zu EXTD_ERC.ULP gedacht, falls Sie vergessen
 *  das Script WARNDEL.SCR einzulesen, bevor Sie EXTD_ERC.ULP ein weiters
 *  Mal starten.
 *  Beachten Sie, dass die Datei WARNDEL.SCR nach einem weiteren Start von
 *  EXTD_ERC.ULP überschrieben wird und Sie die vorhergenden Delete-
 *  Informationen verlieren.
 *
 */

int errlay = 199;           // default Layer for Errors & Warnings to place Symbol(Text)

void Header(string name)
{
  printf("TEXT 'This file is generated by WARNDEL.ULP Version 1.0 from:';\n");
  printf("TEXT '%s';\n", name);
  printf("TEXT 'use this script to delete warnings and errors in layer %d;\n", errlay);
  printf("CHANGE LAYER %d;\n", errlay);
  printf("GRID INCH;\n");
  printf("GRID 0.1;\n");
  printf("DISPLAY NONE;\n");
  printf("LAYER %d;\n", errlay);
}

void Trailer(string name)
{
   printf("LAYER -%d;\n", errlay);
   printf("DISPLAY ALL;\n");
   printf("DISPLAY -93;\n");

}


// main

schematic(SCH) {
  
  output("WARNDEL.SCR", "wt") {     // open Script for delete Warnings & Errors
  Header(SCH.name);
        
  // Check for Text in Layer 199
  
  SCH.sheets(SH) {
    printf("EDIT .S%d;\n", SH.number);
    SH.texts(T) { 
      if (T.layer == errlay) {
        printf("DEL (%6.3f %6.3f);\n", u2inch(T.x - xt), u2inch(T.y - yt));
        }
      }
    }
  Trailer(SCH.name);
  }
 }
