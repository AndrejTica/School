#usage "<qt>This ULP changes the wire width of certain signals in a board and do have "
       "a wire width in between the minimum and maximum values.<p>"
       "Use: run cmd-change-wire-width.ulp<p>\n"
       "NameOff = 1 switches off the checking of net names<p>\n"
       "<hr> "
       "THIS PROGRAM IS PROVIDED AS IS AND WITHOUT WARRANTY OF ANY KIND, EXPRESSED OR IMPLIED.\n"
       "<author>Author: support@cadsoft.de</author></qt>"



string Version = "cmd-change-wire-width.ULP Version 1.4";

string grid[] = { "MIC", "MM", "MIL", "INCH" };
int Gridval = 1;              // 0=mic 1=mm 2=mil 3=inch    ***  
                              // choose the value for the units you're working with

real changewidth =  0.30;     // enter desired width here


int NameOff = 0;       // 0 = change width by name
                       // 1 = change width without name

string signals[]   = { "" };
string chsignals[] = { "" };
int    chngsig     = 0;
int    lastSigCh   = 0;
int decs;

int index[];
int x1[], y1[], x2[], y2[], layer[];
int usedlayer[];
int visibleLayer[];
int n = 1;

string cmd;
string c;

int found(string fnam) {
  int fnd = 0;
  do {
     if (chsignals[fnd] == fnam) {
        return 1;
        break;
        }
     ++fnd;
     } while (chsignals[fnd]);
  return 0;
  }


void disp(int l) {
  sprintf(c, "DISPLAY NONE %d ;\n", l);
  cmd+= c;
  }


void clearlay() {
  for (int ly = 0; ly <= 255; ly++) usedlayer[ly] = 0;
  }


void clearsig (int selct) {
   for (int r = selct; r < lastSigCh; r++) {
      chsignals[r] = chsignals[r + 1];
      }
   chsignals[r + 1] = "";
   if (lastSigCh) lastSigCh--;
   return;
   }


void  AddList (string SigName) {
   int found = 0;
   for (int r = 0; r < lastSigCh; r++) {
      if (chsignals[r] == SigName) {
         found = 1;
         break;
         }
      }
   if (!found) {
      chsignals[r] = SigName;
      lastSigCh++;
      }
   return;
   }


void menue() {
  int cs;
  int l;
  int Result = dlgDialog("Change wire with") {
     string slist[];
     dlgStretch(0);
     dlgLabel("&Signal");
     dlgComboBox(signals, chngsig);
     dlgHBoxLayout {
        dlgStretch(1);
        dlgPushButton("&Add to list") { 
           AddList(signals[chngsig]);
           }
        dlgStretch(1);
        }
     dlgLabel("List signals &to change");
     dlgComboBox(chsignals, decs);
     dlgHBoxLayout {
        dlgStretch(1);
        dlgPushButton("&Delete from list") { 
           clearsig(decs);
           }
        dlgStretch(1);
        }
     dlgGroup("&Grid") {
        dlgRadioButton("m&ic", Gridval);
        dlgRadioButton("&mm", Gridval);
        dlgRadioButton("mi&l", Gridval);
        dlgRadioButton("inc&h", Gridval);
        dlgHBoxLayout {
           dlgStretch(0);
           dlgLabel("new wire &width ");
           dlgStretch(0);
           dlgRealEdit(changewidth);
           dlgStretch(1);
           }
        }
     dlgStretch(1);
     dlgCheckBox("Change all without Signal &name", NameOff);
     dlgHBoxLayout {
        dlgStretch(0);
        dlgPushButton("+&OK") dlgAccept();
        dlgStretch(1);
        dlgPushButton("-&Cancel") dlgReject();
        dlgStretch(0);
        }
     dlgStretch(0);
     };
  if (Result == 0) exit (0);
  return;
  }
  

// main  
if (board) board(B) {
  int s = 0;
  B.signals(S) {
     signals[s] = S.name;
     s++;
     }
  menue();

  clearlay();
  sprintf(c, "GRID %s FINEST;\n", grid[Gridval]);
  cmd+= c;
  sprintf(c, "CHANGE WIDTH %.3f ;\n", changewidth);
  cmd+= c;
   B.signals(S) {
     if (found(S.name) || NameOff) {
       real Wwidth;
       
       S.wires(W) {
         
         switch (Gridval) {
           case 0: Wwidth = u2mic(W.width);
                   break;
           
           case 1: Wwidth = u2mm(W.width);
                   break;
           
           case 2: Wwidth = u2mil(W.width);
                   break;
           
           case 3: Wwidth = u2inch(W.width);
                   break;
           }
         x1[n] = W.x1;
         y1[n] = W.y1;
         x2[n] = W.x2;
         y2[n] = W.y2;
         layer[n] = W.layer;
         ++n;
         }
       }
     }

   sort(n, index, layer);
   int dl = 0;      
   for (int i = 1; i < n; ++i) {
      if(dl != layer[index[i]]) {
        dl = layer[index[i]];
        disp(dl);
        usedlayer[dl] = 1;
        }
      switch (Gridval) {
         case 0: sprintf(c, "CHANGE WIDTH (%.3f %.3f);\n",
                           (u2mic(x1[index[i]]) + u2mic(x2[index[i]])) / 2,
                           (u2mic(y1[index[i]]) + u2mic(y2[index[i]])) / 2 );
                           cmd+= c;
                 break;
         
         case 1: sprintf(c, "CHANGE WIDTH (%.3f %.3f);\n",
                           (u2mm(x1[index[i]]) + u2mm(x2[index[i]])) / 2,
                           (u2mm(y1[index[i]]) + u2mm(y2[index[i]])) / 2 );
                           cmd+= c;
                 break;
         
         case 2: sprintf(c, "CHANGE WIDTH (%.3f %.3f);\n",
                           (u2mil(x1[index[i]]) + u2mil(x2[index[i]])) / 2,
                           (u2mil(y1[index[i]]) + u2mil(y2[index[i]])) / 2 );
                           cmd+= c;
                 break;
         
         case 3: sprintf(c, "CHANGE WIDTH (%.3f %.3f);\n",
                           (u2inch(x1[index[i]]) + u2inch(x2[index[i]])) / 2,
                           (u2inch(y1[index[i]]) + u2inch(y2[index[i]])) / 2 );
                           cmd+= c;
                 break;
         }
      }
   
   cmd += ";\nDISPLAY NONE ";
   B.layers(L) {
      if (L.visible) {
         sprintf(c, "%d", L.number);
         cmd += " " + c;
         }
      }

   sprintf(c, ";\nGRID LAST;\n");
   cmd+= c;
   exit (cmd);
}

else dlgMessageBox("start this ULP in Board", "OK");
